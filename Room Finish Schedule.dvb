Attribute VB_Name = "Room"
Attribute VB_Base = "0{ABDAE97B-BEED-4048-9B63-C849324D8C38}{FC9C16BA-A4C5-4C51-8694-E1166285AE90}"
Attribute VB_GlobalNameSpace = False
Attribute VB_Creatable = False
Attribute VB_PredeclaredId = True
Attribute VB_Exposed = False
Attribute VB_TemplateDerived = False
Attribute VB_Customizable = False
Private Sub Acoustic_Click()

End Sub

Private Sub CheckBox1_Click()


End Sub

Private Sub CheckBox2_Click()

End Sub


Private Sub CommandButton1_Click()
    Room.Hide
    
End Sub

Private Sub CommandButton2_Click()
    Unload Me
    
End Sub

Private Sub Coved_Click()
    If Coved.Value = True Then
        Porcelain_Base.Value = False
        Existing_Base.Value = False
    End If
End Sub

Private Sub Epoxy_Click()

End Sub

Private Sub Exist_Drywall_Click()

End Sub

Private Sub Existing_Base_Click()
    If Existing_Base.Value = True Then
        Porcelain_Base.Value = False
        Coved.Value = False
    End If
End Sub

Private Sub Existing_Ceiling_Click()

End Sub

Private Sub Existing_Floor_Click()
    If Existing_Floor.Value = True Then
        Porcelain_Floor.Value = False
        Quarry.Value = False
    End If
End Sub

Private Sub Existing_Tile_Click()

End Sub

Private Sub Existing_Wall_Click()

End Sub

Private Sub FRP_Click()

End Sub

Private Sub Laminate_Click()

End Sub

Private Sub New_Drywall_Click()

End Sub

Private Sub Paint_Click()

End Sub

Private Sub Porcelain_Base_Click()
    If Porcelain_Base.Value = True Then
        Coved.Value = False
        Existing_Base.Value = False
    End If
End Sub

Private Sub Porcelain_Floor_Click()
    If Porcelain_Floor.Value = True Then
        Quarry.Value = False
        Existing_Floor.Value = False
    End If
End Sub

Private Sub Porcelain_Wall_Click()

End Sub

Private Sub Quarry_Click()
    If Quarry.Value = True Then
        Porcelain_Floor.Value = False
        Existing_Floor.Value = False
    End If
End Sub

Private Sub UserForm_Click()

End Sub

Private Sub Vinyl_Ceiling_Click()

End Sub

Private Sub Vinyl_Click()

End Sub

Private Sub Wallpaper_Click()

End Sub

Attribute VB_Name = "ThisDrawing"
Attribute VB_Base = "0{74D0CE91-F931-4FAC-BEA9-EE32E43EAD37}"
Attribute VB_GlobalNameSpace = False
Attribute VB_Creatable = False
Attribute VB_PredeclaredId = True
Attribute VB_Exposed = True
Attribute VB_TemplateDerived = False
Attribute VB_Customizable = True
Option Explicit

Sub Ch_Add_Table()
    
    ThisDrawing.ActiveLayer = ThisDrawing.Layers("A-Note")
    
    Dim minp As Variant
    Dim maxp As Variant
    Dim pt(2) As Double
    Dim acTable As AcadTable
    
    Set acTable = ThisDrawing.ModelSpace.AddTable(pt, 30, 26, 13.75, 13.25)
    
    With acTable
        .RegenerateTableSuppressed = True
        .RecomputeTableBlock False
        .TitleSuppressed = False
        .HeaderSuppressed = False
        .SetTextStyle AcRowType.acTitleRow, "Arial"
        .SetTextStyle AcRowType.acHeaderRow, "Wendys"
        .SetTextStyle AcRowType.acDataRow, "Wendys"
        Dim i As Double, j As Double
        Dim col As New AcadAcCmColor
        Dim l As Integer
        Dim cell As String
        col.SetRGB 255, 0, 255
        cell = 0

'=======================================================================================================
    'Title
        .SetRowHeight i, 24
        .SetCellTextHeight i, j, 7.5
        .SetCellAlignment i, j, acMiddleCenter
        .SetCellType i, j, acTextCell
        .SetText 0, 0, "ROOM FINISH SCHEDULE"
        
        i = i + 1
        
'=======================================================================================================
    'Header
        For j = 0 To .Columns - 1
        .SetColumnWidth 0, 17.25
        .SetColumnWidth 1, 51.9375
        .MergeCells i, i, 2, 5
        .MergeCells i, i, 6, 9
        .MergeCells i, i, 10, 18
        .MergeCells i, i, 19, 24
        .SetColumnWidth 25, 43.375
        .SetCellTextHeight i, j, 4.5
        .SetCellAlignment i, j, acMiddleCenter
        .SetCellType i, j, acTextCell
        .SetText i, 1, "ROOM"
        .SetText i, 2, "FLOOR"
        .SetText i, 6, "BASE"
        .SetText i, 10, "WALLS"
        .SetText i, 19, "CEILING"
        Next
        
        i = i + 1
        
'=======================================================================================================
    'Data rows
        For j = 0 To .Columns - 1
        
        .SetCellTextHeight i, j, 4.5
        .SetCellAlignment 2, j, acBottomCenter
        .VertCellMargin = 3
        .SetCellType i, j, acTextCell
        .SetTextRotation 2, j, acDegrees090
        .SetRowHeight 2, 81.1875
        .SetColumnWidth 24, 19.1275
        .SetText 2, 0, "SPACE DESIGNATION"
        .SetText 2, 1, ""
        .SetText 2, 2, "NEW PORCELAIN TILE"
        .SetText 2, 3, "QUARRY TILE"
        .SetText 2, 4, ""
        .SetText 2, 5, "EXISTING TO REMAIN"
        .SetText 2, 6, ""
        .SetText 2, 7, "COVED RESILENT"
        .SetText 2, 8, "NEW PORCELAIN TILE"
        .SetText 2, 9, "EXISTING TO REMAIN"
        .SetText 2, 10, "VINYL TILE"
        .SetText 2, 11, "NEW PORCELAIN TILE"
        .SetText 2, 12, "EPOXY PAINT"
        .SetText 2, 13, "LAMINATE PANELING"
        .SetText 2, 14, "PAINT ABOVE NEW WALL TILE"
        .SetText 2, 15, "F.R.P."
        .SetText 2, 16, "VINYL WALL COVERING"
        .SetText 2, 17, "EXISTING WALL TILE TO REMAIN"
        .SetText 2, 18, "EXISTING TO REMAIN U.N.O."
        .SetText 2, 19, "NEW SUSPENDED ACOUSTIC"
        .SetText 2, 20, "NEW SUSPENDED VINYL"
        .SetText 2, 21, "EXISTING DRYWALL - PAINTED"
        .SetText 2, 22, "EXISTING TO REMAIN"
        .SetText 2, 23, "NEW DRYWALL - PAINTED"
        .SetText 2, 24, "HEIGHT"
        .SetText 2, 25, "NOTES"
        
    Next
    
    i = i + 1
    
'=======================================================================================================
'100 Vestibule
    Room.CheckBox1.Value = False
    Room.CheckBox2.Value = False
    Room.CheckBox1.Visible = True
    Room.CheckBox2.Visible = True
    Room.CheckBox1.Caption = "Vestibule"
    Room.CheckBox2.Caption = "Vestibule (2)"
    Room.Porcelain_Floor.Value = False
    Room.Quarry.Value = False
    Room.Existing_Floor.Value = False
    Room.Coved.Value = False
    Room.Porcelain_Base.Value = False
    Room.Existing_Base.Value = False
    Room.Vinyl.Value = False
    Room.Porcelain_Wall.Value = False
    Room.Epoxy.Value = False
    Room.Laminate.Value = False
    Room.Paint.Value = False
    Room.FRP.Value = False
    Room.Wallpaper.Value = False
    Room.Existing_Tile.Value = False
    Room.Existing_Wall.Value = False
    Room.Acoustic.Value = False
    Room.Vinyl_Ceiling.Value = False
    Room.Exist_Drywall.Value = False
    Room.Existing_Ceiling.Value = False
    Room.New_Drywall.Value = False
    Room.Caption = "Vestibule"
    Room.show

'Space Designation and Room Name Cells
    If Room.CheckBox1.Value = True And Room.CheckBox2.Value = False Then
        For j = 0 To 24
            .SetCellTextHeight i, j, 4.5
            .SetCellAlignment i, j, acMiddleCenter
            .SetCellType i, j, acTextCell
            .SetText i, 0, "100"
            .SetText i, 1, "VESTIBULE"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
        Next
'Populates the notes
        For j = 25 To 25
            .SetCellTextHeight i, j, 4.5
            .SetCellAlignment i, j, acMiddleLeft
            .SetCellType i, j, acTextCell
            .HorzCellMargin = 3
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
        Next
        .SetText i, 25, (cell)
'Indents to the next line
        i = i + 1

'=======================================================================================================
'For A and B room set
    ElseIf Room.CheckBox1.Value = True And Room.CheckBox2.Value = True Then
        For i = i To i + 1
            l = l + 1
            For j = 0 To .Columns - 1
            .SetCellTextHeight i, j, 4.5
            .SetCellAlignment i, j, acMiddleCenter
            .SetCellType i, j, acTextCell
            .SetText i, 0, "100" & Chr$(64 + l)
            .SetText i, 1, "VESTIBULE"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
'Populates the notes
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
            Next
            .SetText i, 25, (cell)
        Next
    l = 0
    End If
cell = 0

'=======================================================================================================
'101 Dining Area
    Room.CheckBox1.Value = False
    Room.CheckBox2.Value = False
    Room.CheckBox1.Visible = True
    Room.CheckBox2.Visible = True
    Room.CheckBox1.Caption = "Dining Room"
    Room.CheckBox2.Caption = "Dining Room (2)"
    Room.Porcelain_Floor.Value = False
    Room.Quarry.Value = False
    Room.Existing_Floor.Value = False
    Room.Coved.Value = False
    Room.Porcelain_Base.Value = False
    Room.Existing_Base.Value = False
    Room.Vinyl.Value = False
    Room.Porcelain_Wall.Value = False
    Room.Epoxy.Value = False
    Room.Laminate.Value = False
    Room.Paint.Value = False
    Room.FRP.Value = False
    Room.Wallpaper.Value = False
    Room.Existing_Tile.Value = False
    Room.Existing_Wall.Value = False
    Room.Acoustic.Value = False
    Room.Vinyl_Ceiling.Value = False
    Room.Exist_Drywall.Value = False
    Room.Existing_Ceiling.Value = False
    Room.New_Drywall.Value = False
    Room.Caption = "Dining Area"
    Room.show

'Space Designation and Room Name Cells
    If Room.CheckBox1.Value = True And Room.CheckBox2.Value = False Then
        For j = 0 To 24
            .SetCellTextHeight i, j, 4.5
            .SetCellAlignment i, j, acMiddleCenter
            .SetCellType i, j, acTextCell
            .SetText i, 0, "101"
            .SetText i, 1, "DINING AREA"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
        Next
'Populates the notes
        For j = 25 To 25
            .SetCellTextHeight i, j, 4.5
            .SetCellAlignment i, j, acMiddleLeft
            .SetCellType i, j, acTextCell
            .HorzCellMargin = 3
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
        Next
        .SetText i, 25, (cell)
        i = i + 1

'=======================================================================================================
'For A and B room set
    ElseIf Room.CheckBox1.Value = True And Room.CheckBox2.Value = True Then
        For i = i To i + 1
            l = l + 1
            For j = 0 To .Columns - 1
            .SetCellTextHeight i, j, 4.5
            .SetCellAlignment i, j, acMiddleCenter
            .SetCellType i, j, acTextCell
            .SetText i, 0, "101" & Chr$(64 + l)
            .SetText i, 1, "DINING AREA"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
        'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
        'Ceiling Height Cell
            .SetText i, 24, "EXIST."
'Populates the notes
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
            Next
            .SetText i, 25, (cell)
        Next
    l = 0
    End If
cell = 0

'=======================================================================================================
'102 Service Closet
    Room.CheckBox1.Caption = "Service Closet"
    Room.CheckBox1.Value = False
    Room.CheckBox2.Visible = False
    Room.CheckBox2.Value = False
    Room.Porcelain_Floor.Value = False
    Room.Quarry.Value = False
    Room.Existing_Floor.Value = False
    Room.Coved.Value = False
    Room.Porcelain_Base.Value = False
    Room.Existing_Base.Value = False
    Room.Vinyl.Value = False
    Room.Porcelain_Wall.Value = False
    Room.Epoxy.Value = False
    Room.Laminate.Value = False
    Room.Paint.Value = False
    Room.FRP.Value = False
    Room.Wallpaper.Value = False
    Room.Existing_Tile.Value = False
    Room.Existing_Wall.Value = False
    Room.Acoustic.Value = False
    Room.Vinyl_Ceiling.Value = False
    Room.Exist_Drywall.Value = False
    Room.Existing_Ceiling.Value = False
    Room.New_Drywall.Value = False
    Room.Caption = "Service Closet"
    Room.show

'Space Designation and Room Name Cells
    If Room.CheckBox1.Value = True Then
        For j = 0 To 24
            .SetCellTextHeight i, j, 4.5
            .SetCellAlignment i, j, acMiddleCenter
            .SetCellType i, j, acTextCell
            .SetText i, 0, "102"
            .SetText i, 1, "SERVICE CLOSET"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
        Next
'Populates the notes
        For j = 25 To 25
            .SetCellTextHeight i, j, 4.5
            .SetCellAlignment i, j, acMiddleLeft
            .SetCellType i, j, acTextCell
            .HorzCellMargin = 3
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
        Next
        .SetText i, 25, (cell)
'Indents to the next line
        i = i + 1
    End If
cell = 0

'=======================================================================================================
'103 Women's Room
    Room.CheckBox1.Caption = "Women's Room"
    Room.CheckBox1.Value = False
    Room.CheckBox2.Visible = False
    Room.CheckBox2.Value = False
    Room.Porcelain_Floor.Value = False
    Room.Quarry.Value = False
    Room.Existing_Floor.Value = False
    Room.Coved.Value = False
    Room.Porcelain_Base.Value = False
    Room.Existing_Base.Value = False
    Room.Vinyl.Value = False
    Room.Porcelain_Wall.Value = False
    Room.Epoxy.Value = False
    Room.Laminate.Value = False
    Room.Paint.Value = False
    Room.FRP.Value = False
    Room.Wallpaper.Value = False
    Room.Existing_Tile.Value = False
    Room.Existing_Wall.Value = False
    Room.Acoustic.Value = False
    Room.Vinyl_Ceiling.Value = False
    Room.Exist_Drywall.Value = False
    Room.Existing_Ceiling.Value = False
    Room.New_Drywall.Value = False
    Room.Caption = "Women's Room"
    Room.show

'Space Designation and Room Name Cells
    If Room.CheckBox1.Value = True Then
        For j = 0 To 24
            .SetCellTextHeight i, j, 4.5
            .SetCellAlignment i, j, acMiddleCenter
            .SetCellType i, j, acTextCell
            .SetText i, 0, "103"
            .SetText i, 1, "WOMEN'S ROOM"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
        Next
'Populates the notes
        For j = 25 To 25
            .SetCellTextHeight i, j, 4.5
            .SetCellAlignment i, j, acMiddleLeft
            .SetCellType i, j, acTextCell
            .HorzCellMargin = 3
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
            If Room.CheckBox1.Value = True Then
                cell = (cell) & ",7,8"
            End If
            If Room.Porcelain_Floor.Value = True And Room.Porcelain_Base.Value = True And Room.Porcelain_Wall = True Then
                cell = (cell) & ",9"
            End If
        Next
        .SetText i, 25, (cell)
'Indents to the next line
        i = i + 1
    End If
cell = 0

'=======================================================================================================
'104 Men's Room
    Room.CheckBox1.Caption = "Men's Room"
    Room.CheckBox1.Value = False
    Room.CheckBox2.Visible = False
    Room.CheckBox2.Value = False
    Room.Porcelain_Floor.Value = False
    Room.Quarry.Value = False
    Room.Existing_Floor.Value = False
    Room.Coved.Value = False
    Room.Porcelain_Base.Value = False
    Room.Existing_Base.Value = False
    Room.Vinyl.Value = False
    Room.Porcelain_Wall.Value = False
    Room.Epoxy.Value = False
    Room.Laminate.Value = False
    Room.Paint.Value = False
    Room.FRP.Value = False
    Room.Wallpaper.Value = False
    Room.Existing_Tile.Value = False
    Room.Existing_Wall.Value = False
    Room.Acoustic.Value = False
    Room.Vinyl_Ceiling.Value = False
    Room.Exist_Drywall.Value = False
    Room.Existing_Ceiling.Value = False
    Room.New_Drywall.Value = False
    Room.Caption = "Men's Room"
    Room.show

'Space Designation and Room Name Cells
    If Room.CheckBox1.Value = True Then
        For j = 0 To 24
            .SetCellTextHeight i, j, 4.5
            .SetCellAlignment i, j, acMiddleCenter
            .SetCellType i, j, acTextCell
            .SetText i, 0, "104"
            .SetText i, 1, "MEN'S ROOM"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
        Next
'Populates the notes
        For j = 25 To 25
            .SetCellTextHeight i, j, 4.5
            .SetCellAlignment i, j, acMiddleLeft
            .SetCellType i, j, acTextCell
            .HorzCellMargin = 3
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
            If Room.CheckBox1.Value = True Then
                cell = (cell) & ",7,8"
            End If
            If Room.Porcelain_Floor.Value = True And Room.Porcelain_Base.Value = True And Room.Porcelain_Wall = True Then
                cell = (cell) & ",9"
            End If
        Next
        .SetText i, 25, (cell)
'Indents to the next line
        i = i + 1
    End If
cell = 0

'=======================================================================================================
'105 Service Closet
    Room.CheckBox1.Caption = "Service Area"
    Room.CheckBox1.Value = False
    Room.CheckBox2.Visible = False
    Room.CheckBox2.Value = False
    Room.Porcelain_Floor.Value = False
    Room.Quarry.Value = False
    Room.Existing_Floor.Value = False
    Room.Coved.Value = False
    Room.Porcelain_Base.Value = False
    Room.Existing_Base.Value = False
    Room.Vinyl.Value = False
    Room.Porcelain_Wall.Value = False
    Room.Epoxy.Value = False
    Room.Laminate.Value = False
    Room.Paint.Value = False
    Room.FRP.Value = False
    Room.Wallpaper.Value = False
    Room.Existing_Tile.Value = False
    Room.Existing_Wall.Value = False
    Room.Acoustic.Value = False
    Room.Vinyl_Ceiling.Value = False
    Room.Exist_Drywall.Value = False
    Room.Existing_Ceiling.Value = False
    Room.New_Drywall.Value = False
    Room.Caption = "Service Area"
    Room.show

    'Space Designation and Room Name Cells
    If Room.CheckBox1.Value = True Then
        For j = 0 To 24
            .SetCellTextHeight i, j, 4.5
            .SetCellAlignment i, j, acMiddleCenter
            .SetCellType i, j, acTextCell
            .SetText i, 0, "105"
            .SetText i, 1, "SERVICE AREA"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
        Next
'Populates the notes
        For j = 25 To 25
            .SetCellTextHeight i, j, 4.5
            .SetCellAlignment i, j, acMiddleLeft
            .SetCellType i, j, acTextCell
            .HorzCellMargin = 3
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
        Next
        .SetText i, 25, (cell)
'Indents to the next line
        i = i + 1
    End If
cell = 0

'=======================================================================================================
'106 Drive Thru
    Room.CheckBox1.Value = False
    Room.CheckBox2.Value = False
    Room.CheckBox1.Visible = True
    Room.CheckBox2.Visible = True
    Room.CheckBox1.Caption = "Drive Thru"
    Room.CheckBox2.Caption = "Drive Thru (2)"
    Room.Porcelain_Floor.Value = False
    Room.Quarry.Value = False
    Room.Existing_Floor.Value = False
    Room.Coved.Value = False
    Room.Porcelain_Base.Value = False
    Room.Existing_Base.Value = False
    Room.Vinyl.Value = False
    Room.Porcelain_Wall.Value = False
    Room.Epoxy.Value = False
    Room.Laminate.Value = False
    Room.Paint.Value = False
    Room.FRP.Value = False
    Room.Wallpaper.Value = False
    Room.Existing_Tile.Value = False
    Room.Existing_Wall.Value = False
    Room.Acoustic.Value = False
    Room.Vinyl_Ceiling.Value = False
    Room.Exist_Drywall.Value = False
    Room.Existing_Ceiling.Value = False
    Room.New_Drywall.Value = False
    Room.Caption = "Drive Thru"
    Room.show

'Space Designation and Room Name Cells
    If Room.CheckBox1.Value = True And Room.CheckBox2.Value = False Then
        For j = 0 To 24
            .SetCellTextHeight i, j, 4.5
            .SetCellAlignment i, j, acMiddleCenter
            .SetCellType i, j, acTextCell
            .SetText i, 0, "100"
            .SetText i, 1, "DRIVE THRU"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
        Next
'Populates the notes
        For j = 25 To 25
            .SetCellTextHeight i, j, 4.5
            .SetCellAlignment i, j, acMiddleLeft
            .SetCellType i, j, acTextCell
            .HorzCellMargin = 3
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
        Next
        .SetText i, 25, (cell)
'Indents to the next line
        i = i + 1

'=======================================================================================================
'For A and B room set
    ElseIf Room.CheckBox1.Value = True And Room.CheckBox2.Value = True Then
        For i = i To i + 1
            l = l + 1
            For j = 0 To .Columns - 1
            .SetCellTextHeight i, j, 4.5
            .SetCellAlignment i, j, acMiddleCenter
            .SetCellType i, j, acTextCell
            .SetText i, 0, "106" & Chr$(64 + l)
            .SetText i, 1, "DRIVE THRU"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
        'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
        'Ceiling Height Cell
            .SetText i, 24, "EXIST."
'Populates the notes
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
            Next
            .SetText i, 25, (cell)
        Next
    l = 0
    End If
cell = 0

'=======================================================================================================
'107 Preperation Area
    Room.CheckBox1.Caption = "Preperation Area"
    Room.CheckBox1.Value = False
    Room.CheckBox2.Visible = False
    Room.CheckBox2.Value = False
    Room.Porcelain_Floor.Value = False
    Room.Quarry.Value = False
    Room.Existing_Floor.Value = False
    Room.Coved.Value = False
    Room.Porcelain_Base.Value = False
    Room.Existing_Base.Value = False
    Room.Vinyl.Value = False
    Room.Porcelain_Wall.Value = False
    Room.Epoxy.Value = False
    Room.Laminate.Value = False
    Room.Paint.Value = False
    Room.FRP.Value = False
    Room.Wallpaper.Value = False
    Room.Existing_Tile.Value = False
    Room.Existing_Wall.Value = False
    Room.Acoustic.Value = False
    Room.Vinyl_Ceiling.Value = False
    Room.Exist_Drywall.Value = False
    Room.Existing_Ceiling.Value = False
    Room.New_Drywall.Value = False
    Room.Caption = "Preperation Area"
    Room.show

    'Space Designation and Room Name Cells
    If Room.CheckBox1.Value = True Then
        For j = 0 To 24
            .SetCellTextHeight i, j, 4.5
            .SetCellAlignment i, j, acMiddleCenter
            .SetCellType i, j, acTextCell
            .SetText i, 0, "107"
            .SetText i, 1, "PREPERATION AREA"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
        Next
'Populates the notes
        For j = 25 To 25
            .SetCellTextHeight i, j, 4.5
            .SetCellAlignment i, j, acMiddleLeft
            .SetCellType i, j, acTextCell
            .HorzCellMargin = 3
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
        Next
        .SetText i, 25, (cell)
'Indents to the next line
        i = i + 1
    End If
cell = 0

'=======================================================================================================
'109 Office
    Room.CheckBox1.Caption = "Office"
    Room.CheckBox1.Value = False
    Room.CheckBox2.Visible = False
    Room.CheckBox2.Value = False
    Room.Porcelain_Floor.Value = False
    Room.Quarry.Value = False
    Room.Existing_Floor.Value = False
    Room.Coved.Value = False
    Room.Porcelain_Base.Value = False
    Room.Existing_Base.Value = False
    Room.Vinyl.Value = False
    Room.Porcelain_Wall.Value = False
    Room.Epoxy.Value = False
    Room.Laminate.Value = False
    Room.Paint.Value = False
    Room.FRP.Value = False
    Room.Wallpaper.Value = False
    Room.Existing_Tile.Value = False
    Room.Existing_Wall.Value = False
    Room.Acoustic.Value = False
    Room.Vinyl_Ceiling.Value = False
    Room.Exist_Drywall.Value = False
    Room.Existing_Ceiling.Value = False
    Room.New_Drywall.Value = False
    Room.Caption = "Office"
    Room.show

'Space Designation and Room Name Cells
    If Room.CheckBox1.Value = True Then
        For j = 0 To 24
            .SetCellTextHeight i, j, 4.5
            .SetCellAlignment i, j, acMiddleCenter
            .SetCellType i, j, acTextCell
            .SetText i, 0, "109"
            .SetText i, 1, "OFFICE"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
           If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
        Next
'Populates the notes
        For j = 25 To 25
            .SetCellTextHeight i, j, 4.5
            .SetCellAlignment i, j, acMiddleLeft
            .SetCellType i, j, acTextCell
            .HorzCellMargin = 3
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
        Next
        .SetText i, 25, (cell)
'Indents to the next line
        i = i + 1
    End If
cell = 0

'=======================================================================================================
'110 Break Area
    Room.CheckBox1.Caption = "Break Area"
    Room.CheckBox1.Value = False
    Room.CheckBox2.Visible = False
    Room.CheckBox2.Value = False
    Room.Porcelain_Floor.Value = False
    Room.Quarry.Value = False
    Room.Existing_Floor.Value = False
    Room.Coved.Value = False
    Room.Porcelain_Base.Value = False
    Room.Existing_Base.Value = False
    Room.Vinyl.Value = False
    Room.Porcelain_Wall.Value = False
    Room.Epoxy.Value = False
    Room.Laminate.Value = False
    Room.Paint.Value = False
    Room.FRP.Value = False
    Room.Wallpaper.Value = False
    Room.Existing_Tile.Value = False
    Room.Existing_Wall.Value = False
    Room.Acoustic.Value = False
    Room.Vinyl_Ceiling.Value = False
    Room.Exist_Drywall.Value = False
    Room.Existing_Ceiling.Value = False
    Room.New_Drywall.Value = False
    Room.Caption = "Break Area"
    Room.show

'Space Designation and Room Name Cells
    If Room.CheckBox1.Value = True Then
        For j = 0 To 24
            .SetCellTextHeight i, j, 4.5
            .SetCellAlignment i, j, acMiddleCenter
            .SetCellType i, j, acTextCell
            .SetText i, 0, "110"
            .SetText i, 1, "BREAK AREA"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
           If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
        Next
'Populates the notes
        For j = 25 To 25
            .SetCellTextHeight i, j, 4.5
            .SetCellAlignment i, j, acMiddleLeft
            .SetCellType i, j, acTextCell
            .HorzCellMargin = 3
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
        Next
        .SetText i, 25, (cell)
'Indents to the next line
        i = i + 1
    End If
cell = 0

'=======================================================================================================
'111 Dishwashing Area
    Room.CheckBox1.Caption = "Dishwashing Area"
    Room.CheckBox1.Value = False
    Room.CheckBox2.Visible = False
    Room.CheckBox2.Value = False
    Room.Porcelain_Floor.Value = False
    Room.Quarry.Value = False
    Room.Existing_Floor.Value = False
    Room.Coved.Value = False
    Room.Porcelain_Base.Value = False
    Room.Existing_Base.Value = False
    Room.Vinyl.Value = False
    Room.Porcelain_Wall.Value = False
    Room.Epoxy.Value = False
    Room.Laminate.Value = False
    Room.Paint.Value = False
    Room.FRP.Value = False
    Room.Wallpaper.Value = False
    Room.Existing_Tile.Value = False
    Room.Existing_Wall.Value = False
    Room.Acoustic.Value = False
    Room.Vinyl_Ceiling.Value = False
    Room.Exist_Drywall.Value = False
    Room.Existing_Ceiling.Value = False
    Room.New_Drywall.Value = False
    Room.Caption = "Dishwashing Area"
    Room.show

'Space Designation and Room Name Cells
    If Room.CheckBox1.Value = True Then
        For j = 0 To 24
            .SetCellTextHeight i, j, 4.5
            .SetCellAlignment i, j, acMiddleCenter
            .SetCellType i, j, acTextCell
            .SetText i, 0, "111"
            .SetText i, 1, "DISHWASHING AREA"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
        Next
'Populates the notes
        For j = 25 To 25
            .SetCellTextHeight i, j, 4.5
            .SetCellAlignment i, j, acMiddleLeft
            .SetCellType i, j, acTextCell
            .HorzCellMargin = 3
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
        Next
        .SetText i, 25, (cell)
        i = i + 1
    End If
cell = 0

'=======================================================================================================
'112 Walk-In Cooler
    Room.CheckBox1.Value = False
    Room.CheckBox2.Value = False
    Room.CheckBox1.Visible = True
    Room.CheckBox2.Visible = True
    Room.CheckBox1.Caption = "Walk-in Cooler"
    Room.CheckBox2.Caption = "Walk-in Cooler (2)"
    Room.Porcelain_Floor.Value = False
    Room.Quarry.Value = False
    Room.Existing_Floor.Value = False
    Room.Coved.Value = False
    Room.Porcelain_Base.Value = False
    Room.Existing_Base.Value = False
    Room.Vinyl.Value = False
    Room.Porcelain_Wall.Value = False
    Room.Epoxy.Value = False
    Room.Laminate.Value = False
    Room.Paint.Value = False
    Room.FRP.Value = False
    Room.Wallpaper.Value = False
    Room.Existing_Tile.Value = False
    Room.Existing_Wall.Value = False
    Room.Acoustic.Value = False
    Room.Vinyl_Ceiling.Value = False
    Room.Exist_Drywall.Value = False
    Room.Existing_Ceiling.Value = False
    Room.New_Drywall.Value = False
    Room.Caption = "Walk-in Cooler"
    Room.show

'Space Designation and Room Name Cells
    If Room.CheckBox1.Value = True And Room.CheckBox2.Value = False Then
        For j = 0 To 24
            .SetCellTextHeight i, j, 4.5
            .SetCellAlignment i, j, acMiddleCenter
            .SetCellType i, j, acTextCell
            .SetText i, 0, "112"
            .SetText i, 1, "WALK-IN COOLER"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
        Next
'Populates the notes
        For j = 25 To 25
            .SetCellTextHeight i, j, 4.5
            .SetCellAlignment i, j, acMiddleLeft
            .SetCellType i, j, acTextCell
            .HorzCellMargin = 3
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
        Next
        .SetText i, 25, (cell)
'Indents to the next line
        i = i + 1

'=======================================================================================================
'For A and B room set
    ElseIf Room.CheckBox1.Value = True And Room.CheckBox2.Value = True Then
        For i = i To i + 1
            l = l + 1
            For j = 0 To .Columns - 1
            .SetCellTextHeight i, j, 4.5
            .SetCellAlignment i, j, acMiddleCenter
            .SetCellType i, j, acTextCell
            .SetText i, 0, "112" & Chr$(64 + l)
            .SetText i, 1, "WALK-IN COOLER"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
'Populates the notes
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
            Next
            .SetText i, 25, (cell)
        Next
    l = 0
    End If
cell = 0

'=======================================================================================================
'113 Wallk-In Freezer
    Room.CheckBox1.Value = False
    Room.CheckBox2.Value = False
    Room.CheckBox1.Visible = True
    Room.CheckBox2.Visible = True
    Room.CheckBox1.Caption = "Walk-in Freezer"
    Room.CheckBox2.Caption = "Walk-in Freezer (2)"
    Room.Porcelain_Floor.Value = False
    Room.Quarry.Value = False
    Room.Existing_Floor.Value = False
    Room.Coved.Value = False
    Room.Porcelain_Base.Value = False
    Room.Existing_Base.Value = False
    Room.Vinyl.Value = False
    Room.Porcelain_Wall.Value = False
    Room.Epoxy.Value = False
    Room.Laminate.Value = False
    Room.Paint.Value = False
    Room.FRP.Value = False
    Room.Wallpaper.Value = False
    Room.Existing_Tile.Value = False
    Room.Existing_Wall.Value = False
    Room.Acoustic.Value = False
    Room.Vinyl_Ceiling.Value = False
    Room.Exist_Drywall.Value = False
    Room.Existing_Ceiling.Value = False
    Room.New_Drywall.Value = False
    Room.Caption = "walk-in Freezer"
    Room.show

'Space Designation and Room Name Cells
    If Room.CheckBox1.Value = True And Room.CheckBox2.Value = False Then
        For j = 0 To 24
            .SetCellTextHeight i, j, 4.5
            .SetCellAlignment i, j, acMiddleCenter
            .SetCellType i, j, acTextCell
            .SetText i, 0, "113"
            .SetText i, 1, "WALK-IN FREEZER"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
        Next
'Populates the notes
        For j = 25 To 25
            .SetCellTextHeight i, j, 4.5
            .SetCellAlignment i, j, acMiddleLeft
            .SetCellType i, j, acTextCell
            .HorzCellMargin = 3
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
        Next
        .SetText i, 25, (cell)
'Indents to the next line
        i = i + 1

'=======================================================================================================
'For A and B room set
    ElseIf Room.CheckBox1.Value = True And Room.CheckBox2.Value = True Then
        For i = i To i + 1
            l = l + 1
            For j = 0 To .Columns - 1
            .SetCellTextHeight i, j, 4.5
            .SetCellAlignment i, j, acMiddleCenter
            .SetCellType i, j, acTextCell
            .SetText i, 0, "113" & Chr$(64 + l)
            .SetText i, 1, "WALK-IN FREEZER"
'Floor Finish Cells
            If Room.Porcelain_Floor.Value = True Then
                .SetText i, 2, "\U+25CF"
            ElseIf Room.Quarry.Value = True Then
                .SetText i, 3, "\U+25CF"
            ElseIf Room.Existing_Floor.Value = True Then
                .SetText i, 5, "\U+25CF"
            End If
'Base Finish Cells
            If Room.Coved.Value = True Then
                .SetText i, 7, "\U+25CF"
            ElseIf Room.Porcelain_Base.Value = True Then
                .SetText i, 8, "\U+25CF"
            ElseIf Room.Existing_Base.Value = True Then
                .SetText i, 9, "\U+25CF"
            End If
'Wall Finish Cells
            If Room.Vinyl.Value = True Then
                .SetText i, 10, "\U+25CF"
            End If
            If Room.Porcelain_Wall.Value = True Then
                .SetText i, 11, "\U+25CF"
            End If
            If Room.Epoxy.Value = True Then
                .SetText i, 12, "\U+25CF"
            End If
            If Room.Laminate.Value = True Then
                .SetText i, 13, "\U+25CF"
            End If
            If Room.Paint.Value = True Then
                .SetText i, 14, "\U+25CF"
            End If
            If Room.FRP.Value = True Then
                .SetText i, 15, "\U+25CF"
            End If
            If Room.Wallpaper.Value = True Then
                .SetText i, 16, "\U+25CF"
            End If
            If Room.Existing_Tile.Value = True Then
                .SetText i, 17, "\U+25CF"
            End If
            If Room.Existing_Wall.Value = True Then
                .SetText i, 18, "\U+25CF"
            End If
'Ceiling Finish Cells
            If Room.Acoustic.Value = True Then
                .SetText i, 19, "\U+25CF"
            End If
            If Room.Vinyl_Ceiling.Value = True Then
                .SetText i, 20, "\U+25CF"
            End If
            If Room.Exist_Drywall.Value = True Then
                .SetText i, 21, "\U+25CF"
            End If
            If Room.Existing_Ceiling.Value = True Then
                .SetText i, 22, "\U+25CF"
            End If
            If Room.New_Drywall.Value = True Then
                .SetText i, 23, "\U+25CF"
            End If
'Ceiling Height Cell
            .SetText i, 24, "EXIST."
'Populates the notes
            If Room.Porcelain_Floor.Value = True Or Room.Quarry.Value = True Then
                cell = 1
            End If
            If Room.Existing_Ceiling.Value = True Then
                If cell = 0 Then
                    cell = 2
                Else
                    cell = (cell) & ",2"
                End If
            End If
            If Room.Existing_Wall.Value = False Then
                cell = (cell) & ",3"
            End If
            If Room.FRP.Value = False And Room.Existing_Wall.Value = True Then
                cell = (cell) & ",4"
            End If
            If Room.Acoustic.Value = True Or Room.Vinyl_Ceiling.Value = True Then
                cell = (cell) & ",5"
            End If
            If Room.Existing_Floor.Value = True Then
                cell = (cell) & ",6"
            End If
            Next
            .SetText i, 25, (cell)
        Next
    l = 0
    End If
cell = 0

'=======================================================================================================
    'Deletes all unused rows
    .DeleteRows i, .Rows - 1

'=======================================================================================================
    ' set color for grid
    'TITLE
        col.SetRGB 255, 0, 255
        .SetGridColor AcGridLineType.acHorzBottom, AcRowType.acTitleRow, col
        .SetGridColor AcGridLineType.acHorzInside, AcRowType.acTitleRow, col
        .SetGridColor AcGridLineType.acHorzTop, AcRowType.acTitleRow, col
        .SetGridColor AcGridLineType.acVertInside, AcRowType.acTitleRow, col
        .SetGridColor AcGridLineType.acVertLeft, AcRowType.acTitleRow, col
        .SetGridColor AcGridLineType.acVertRight, AcRowType.acTitleRow, col
    'HEADER
        col.SetRGB 255, 0, 255
        .SetGridColor AcGridLineType.acHorzTop, AcRowType.acHeaderRow, col
        .SetGridColor AcGridLineType.acVertLeft, AcRowType.acHeaderRow, col
        .SetGridColor AcGridLineType.acVertRight, AcRowType.acHeaderRow, col
        col.SetRGB 0, 255, 255
        .SetGridColor AcGridLineType.acHorzBottom, AcRowType.acHeaderRow, col
        .SetGridColor AcGridLineType.acHorzInside, AcRowType.acHeaderRow, col
        .SetGridColor AcGridLineType.acVertInside, AcRowType.acHeaderRow, col
    'ROW
        col.SetRGB 255, 0, 255
        .SetGridColor AcGridLineType.acHorzBottom, AcRowType.acDataRow, col
        .SetGridColor AcGridLineType.acVertLeft, AcRowType.acDataRow, col
        .SetGridColor AcGridLineType.acVertRight, AcRowType.acDataRow, col
        col.SetRGB 0, 255, 255
        .SetGridColor AcGridLineType.acHorzInside, AcRowType.acDataRow, col
        .SetGridColor AcGridLineType.acHorzTop, AcRowType.acDataRow, col
        col.SetRGB 255, 255, 0
        .SetGridColor AcGridLineType.acVertInside, AcRowType.acDataRow, col
    
    'set line weights for grid
        .SetGridLineWeight AcGridLineType.acVertLeft, AcRowType.acTitleRow, AcLineWeight.acLnWtByLayer
        .SetGridLineWeight AcGridLineType.acVertRight, AcRowType.acTitleRow, AcLineWeight.acLnWtByLayer
        .SetGridLineWeight AcGridLineType.acHorzTop, AcRowType.acTitleRow, AcLineWeight.acLnWtByLayer
        .SetGridLineWeight AcGridLineType.acHorzBottom, AcRowType.acHeaderRow, AcLineWeight.acLnWtByLayer
        .SetGridLineWeight AcGridLineType.acHorzInside, AcRowType.acHeaderRow, AcLineWeight.acLnWtByLayer
        .SetGridLineWeight AcGridLineType.acHorzTop, AcRowType.acHeaderRow, AcLineWeight.acLnWtByLayer
        .SetGridLineWeight AcGridLineType.acVertInside, AcRowType.acHeaderRow, AcLineWeight.acLnWtByLayer
        .SetGridLineWeight AcGridLineType.acVertLeft, AcRowType.acHeaderRow, AcLineWeight.acLnWtByLayer
        .SetGridLineWeight AcGridLineType.acVertRight, AcRowType.acHeaderRow, AcLineWeight.acLnWtByLayer
        .SetGridLineWeight AcGridLineType.acHorzBottom, AcRowType.acDataRow, AcLineWeight.acLnWtByLayer
        .SetGridLineWeight AcGridLineType.acHorzInside, AcRowType.acDataRow, AcLineWeight.acLnWtByLayer
        .SetGridLineWeight AcGridLineType.acHorzTop, AcRowType.acDataRow, AcLineWeight.acLnWtByLayer
        .SetGridLineWeight AcGridLineType.acVertInside, AcRowType.acDataRow, AcLineWeight.acLnWtByLayer
        .SetGridLineWeight AcGridLineType.acVertLeft, AcRowType.acDataRow, AcLineWeight.acLnWtByLayer
        .SetGridLineWeight AcGridLineType.acVertRight, AcRowType.acDataRow, AcLineWeight.acLnWtByLayer

'=======================================================================================================
    .RegenerateTableSuppressed = False
    .RecomputeTableBlock True
    .Update

    .GetBoundingBox minp, maxp
    ZoomWindow minp, maxp
    ZoomScaled 0.9, acZoomScaledRelative

Set col = Nothing
Set Room = Nothing
End With

End Sub

Private Sub Class_Initialize()
    
End Sub
